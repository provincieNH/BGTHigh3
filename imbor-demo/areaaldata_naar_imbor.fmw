FME workspace areaaldata_naar_imbor.fmw

Parameters:
- SourceDataset_GEODATABASE_FILE = D:\BGT-HIGH3\InspectieWegdelen.gdb   # File Geodatabase
- SourceDataset_FILEGDB = D:\BGT-HIGH3\InspectieWegdelen.gdb   # File Geodatabase
- DestDataset_TEXTLINE = D:\BGT-HIGH3\imbor3.rdf   # Destination Text File
- DestDataset_TEXTLINE_3 = D:\BGT-HIGH3\inspecties2.rdf   # Destination Text File

Readers:
- GEODATABASE_FILE_1: GEODATABASE_FILE from $(SourceDataset_GEODATABASE_FILE)
- FILEGDB_1: FILEGDB from $(SourceDataset_FILEGDB)
- GEODATABASE_SDE_1: GEODATABASE_SDE

Writers:
- TEXTLINE_1: TEXTLINE to $(DestDataset_TEXTLINE)
- TEXTLINE_2: TEXTLINE to $(DestDataset_TEXTLINE_3)

wegdeel_v (reader GEODATABASE_FILE_1)
    attributes: OBJECTID integer, GLOBALID char(38), FYSIEKVOORKOMEN char(255), FUNCTIE char(50), OPTALUD char(255), IDENTIFICATIE char(255), STATUS char(255), BRONHOUDER char(255), INONDERZOEK char(255), RELATIEVEHOOGTELIGGING smallint, TIJDSTIPREGISTRATIE date, EINDREGISTRATIE date, LV_PUBLICATIEDATUM date, BERICHT_ID char(255), TYPESPEC char(255), VERWERKINGSSTATUS char(255), GISIB_ID integer, AD_ID char(255), OBJECTBEGINTIJD date, OBJECTEINDTIJD date, CREATED_USER char(255), CREATED_DATE date, LAST_EDITED_USER char(50), LAST_EDITED_DATE date, BEHEERDER char(255), ONDERHOUDER char(255), EIGENAAR char(255), DATALEVERANCIER char(255), BREEDTE double, COMFORT char(255),
      COMFORT_DATE date, DEFLECTIE char(255), DEFLECTIE_DATE date, KOMGRENS char(255), WEGTYPE char(255), WEGINDELING char(255), JAARAANLEG smallint, JAARDEKLAAG smallint, JAARHERSTRATEN smallint, JAARVERNIEUWEN smallint, LANGSONVLAKHEID char(255), LANGSONVLAKHEID_DATE date, LENGTEVOEGEN smallint, SPOORVORMING char(255), SPOORVORMING_DATE date, GEBRUIKSFUNCTIE char(255), SITUERING char(255), STROEFHEID char(255), STROEFHEID_DATE date, VERHARDING char(255), VERHARDINGCATEGORIE char(255), WGV_AFSTANDTOT double, WGV_AFSTANDVAN double, WGV_NUMMER smallint, HALTE char(255), WEGVAK char(255), TRAJECT char(255), VERLICHT char(255), HECTOMETER char(255), DWARSONVLAKHEID char(50),
      DWARSONVLAKHEID_DATE date, INSPECTEUR char(50), LENGTE smallint, OPMERKING char(255), OMTREK double, OPPERVLAKTE double, SHAPE_Length double, SHAPE_Area double
    -> wegdeel_v
    -> FeatureMerger [REQUESTOR]
wegdeel_v: Inspector
traject_v (reader GEODATABASE_SDE_1)
    attributes: OBJECTID integer, GLOBALID char(38), CODE char(25), GEBRUIKSFUNCTIE char(255), PLANJAAR smallint, RANGORDE smallint, AANLEGJAAR smallint, BEGINLINKEROEVER char(255), BEGINRECHTEROEVER char(255), BEPERKING char(255), EINDLINKEROEVER char(255), EINDRECHTEROEVER char(255), JAARAANLEG smallint, LENGTELINKEROEVER double, LENGTERECHTEROEVER double, STREEFBEELD char(255), VOLDOET smallint, CEMTKLASSE char(255), MAATGEVENDSCHIP char(255), GEBIEDSCONTRACTREGIO char(255), TYPESPEC char(255), VERWERKINGSSTATUS char(255), GISIB_ID integer, AD_ID char(255), OBJECTBEGINTIJD date, OBJECTEINDTIJD date, CREATED_USER char(255), CREATED_DATE date, LAST_EDITED_USER char(50), LAST_EDITED_DATE date,
      DATALEVERANCIER char(255), OPMERKING char(255), OMTREK double, OPPERVLAKTE double, SHAPE.STArea() double, SHAPE.STLength() double
    -> AttributeRenamer_2
AttributeRenamer_2
    ATTR_TABLE = RENAME_SET_DEFAULT AD_ID > TRAJ_ID
    -> AttributeKeeper
AttributeKeeper
    KEEP_ATTRS = CODE,TRAJ_ID
    -> FeatureMerger [SUPPLIER]
FeatureMerger
    ATTR_ACCUM_MODE = Merge Supplier
    ATTR_CONFLICT_RES = Use Requestor
    IGNORE_NULLS = No
    JOIN_KEYS = @Value(TRAJECT) @Value(TRAJ_ID) AUTO
    MERGE_TYPE = Attributes Only
    PROCESS_DUPS = NO
    REJECT_NULL_MISSING_KEYS = No
    SUPPLIERS_FIRST = No
    MERGED -> AttributeValueMapper
    UNMERGED_REQUESTOR -> AttributeValueMapper
    <REJECTED> -> ListIndexer__Rejected_
AttributeValueMapper
    DEFAULT_VALUE = Objecttypes_401
    DIRECTION = Forward (Source To Destination)
    LUT = Basalt,TypePlus2_18,Beton,TypePlus_1136,Bitumen,Type_850,FME_NULL_VALUE,Objecttypes_401,Geen,Objecttypes_401,Groenstenen,Type_851,Halfverhard,Type_852,Klinkers,TypePlus_1126,Onbekend,Objecttypes_401,Tegels,TypePlus_1129
    SRC = VERHARDINGCATEGORIE
    VAL_ATTR = verh_cat
    -> StringConcatenator
Note: uri
StringConcatenator
    ACTION = Create New Attribute
    PARM_LINE = http://connecteddata.nl/imbor/id/data/@Value(AD_ID)
    VAL_ATTR = uri
    -> AttributeCopier
    -> AttributeSplitter
AttributeCopier
    ATTR_TABLE = COPY IDENTIFICATIE > lokaalid
    -> StringReplacer
StringReplacer
    CASE = NO
    FIND_TEXT = NL.IMGEO.
    NO_MATCH = _FME_NO_OP_
    REGEXP = NO
    SRC_ATTRS = lokaalid
    -> DateTimeConverter
DateTimeConverter
    DATETIME_ATTR = LANGSONVLAKHEID_DATE SPOORVORMING_DATE DWARSONVLAKHEID_DATE
    OUT_FORMAT = ISO
    PASSTHROUGH = YES
    REPAIR_INPUT = YES
    -> StringConcatenator_2
    <REJECTED> -> StringConcatenator_2
AttributeSplitter [off]
    ATTR_NAME = IDENTIFICATIE
    DELIMITER = .
    DROP_EMPTY_PARTS = Yes
    LIST_NAME = _list
    TRIM_OPTION = Both
    -> ListIndexer
ListIndexer [off]
    INDEX = 3
    LIST_ATTR = _list{}
    -> AttributeRenamer
    <REJECTED> -> ListIndexer__Rejected_
ListIndexer__Rejected_: Inspector [off]
AttributeRenamer [off]
    ATTR_TABLE = RENAME_SET_DEFAULT _list > lokaalid
    -> StringConcatenator_2
Note: gebruiksfunctie
StringConcatenator_2
    ACTION = Create New Attribute
    PARM_LINE = http://connecteddata.nl/bgt/def/waardenlijst/@Value(GEBRUIKSFUNCTIE)
    VAL_ATTR = gebruiksfunctie_uri
    -> XMLTemplater [SUB]
Export_Output_2 (reader FILEGDB_1) [off]
    attributes: OBJECTID objectid, GLOBALID globalid, VERWERKINGSSTATUS text(255), SCHADESOORT text(10), SCHADEWAARDE text(10), SCHADECODE text(10), OPMERKING text(10), WVO_ID text(255), INSP_ID text(255), IDENTIFICATIE text(255), GISIB_ID int, AD_ID text(255), OBJECTBEGINTIJD date, OBJECTEINDTIJD date, CREATED_USER text(255), CREATED_DATE date, LAST_EDITED_USER text(50), LAST_EDITED_DATE date, DATALEVERANCIER text(255)
    -> Export_Output_2
    -> StringConcatenator_3
Export_Output_2: Inspector [off]
Note: uri
StringConcatenator_3 [off]
    ACTION = Create New Attribute
    PARM_LINE = http://connecteddata.nl/areaaldata/weginspectie/@Value(AD_ID)
    VAL_ATTR = uri
    -> StringConcatenator_4
Note: uri
StringConcatenator_4 [off]
    ACTION = Create New Attribute
    PARM_LINE = http://connecteddata.nl/imbor/id/data/@Value(WVO_ID)
    VAL_ATTR = hoortBij
    -> XMLTemplater_2 [SUB]
Export_Output (reader FILEGDB_1) [off]
    attributes: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
Creator
    GEOMTYPE = Geometry Object
    NUM = 1
    CREATED -> XMLTemplater [ROOT]
    CREATED -> XMLTemplater_2 [ROOT]
Note: Merge feature values into XML template
XMLTemplater_2 [off]
    OUTPUT_XML_HEADER = Yes
    RESULT_ATTRIBUTE = text_line_data
    ROOT_QUERY_EXPR:
      <?xml version="1.0"?>
      <rdf:RDF
          xmlns:otl="http://linkeddata.crow.nl/otl-bim-pro-imbor/def/objecttype/"
          xmlns:rdf="http://www.w3.org/1999/02/22-rdf-syntax-ns#"
          xmlns:bgt="http://connecteddata.nl/bgt/def/objecttype/"
          xmlns:insp="http://connecteddata.nl/areaaldata/weginspectie/"
          xmlns:p="http://linkeddata.crow.nl/otl-bim-pro-imbor/def/prop/"
          xmlns:demo-data="http://connecteddata.nl/imbor/id/data/"
          xmlns:owl="http://www.w3.org/2002/07/owl#"
          xmlns:geo="http://www.opengis.net/ont/geosparql#"
          xmlns:otlvwl="http://linkeddata.crow.nl/otl-bim-pro-imbor/def/vastewaardelijst/"
          xmlns:rdfs="http://www.w3.org/2000/01/rdf-schema#"
          xmlns:sf="http://www.opengis.net/ont/sf#"
          xmlns:xsd="http://www.w3.org/2001/XMLSchema#"
        xml:base="http://connecteddata.nl/imbor/id/data/" >
        <owl:Ontology rdf:about="">
          <owl:imports rdf:resource="http://linkeddata.crow.nl/otl-bim-pro-imbor/"/>
        </owl:Ontology>
        {fme:process-features("SUB")}
        </rdf:RDF>
    SUB_QUERY_EXPR:
        <rdf:Description rdf:about="{fme:get-attribute("uri")}">
          <insp:schadesoort>{fme:get-attribute("SCHADESOORT")}</insp:schadesoort>
          <insp:schadewaarde>{fme:get-attribute("SCHADEWAARDE")}</insp:schadewaarde>
          <insp:schadecode>{fme:get-attribute("SCHADECODE")}</insp:schadecode>
          <rdf:type rdf:resource="insp:Inspectie"/>
          <rdfs:label>{fme:get-attribute("IDENTIFICATIE")}</rdfs:label>
          <insp:hoortBij rdf:resource="{fme:get-attribute("hoortBij")}"/>
        </rdf:Description>
    VISIBLE_QUERY_VALIDATE = Yes
    -> XMLFormatter_2
Note: Pretty-print and check validity
XMLFormatter_2 [off]
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = text_line_data
    XML_INPUT_TYPE = Attribute Specifying XML Text
    XML_OUTPUT_ATTR = text_line_data
    XML_OUTPUT_TYPE = Attribute
    PASSED -> XMLFormatter_2_Passed
    PASSED -> text_line (writer TEXTLINE_2)
    FAILED -> XMLFormatter_2_Failed
XMLFormatter_2_Passed: Inspector [off]
XMLFormatter_2_Failed: Inspector [off]
text_line (writer TEXTLINE_2) [off]
    attributes: text_line_data buffer
Note: Merge feature values into XML template
XMLTemplater
    OUTPUT_XML_HEADER = Yes
    RESULT_ATTRIBUTE = text_line_data
    ROOT_QUERY_EXPR:
      <?xml version="1.0"?>
      <rdf:RDF
          xmlns:otl="http://linkeddata.crow.nl/otl-bim-pro-imbor/def/objecttype/"
          xmlns:rdf="http://www.w3.org/1999/02/22-rdf-syntax-ns#"
          xmlns:bgt="http://connecteddata.nl/bgt/def/objecttype/"
          xmlns:p="http://linkeddata.crow.nl/otl-bim-pro-imbor/def/prop/"
          xmlns:demo-data="http://connecteddata.nl/imbor/id/data/"
          xmlns:owl="http://www.w3.org/2002/07/owl#"
          xmlns:geo="http://www.opengis.net/ont/geosparql#"
          xmlns:otlvwl="http://linkeddata.crow.nl/otl-bim-pro-imbor/def/vastewaardelijst/"
          xmlns:rdfs="http://www.w3.org/2000/01/rdf-schema#"
          xmlns:sf="http://www.opengis.net/ont/sf#"
          xmlns:xsd="http://www.w3.org/2001/XMLSchema#"
        xml:base="http://connecteddata.nl/imbor/id/data/" >
        <owl:Ontology rdf:about="">
          <owl:imports rdf:resource="http://linkeddata.crow.nl/otl-bim-pro-imbor/"/>
        </owl:Ontology>
        {fme:process-features("SUB")}
        </rdf:RDF>
    SUB_QUERY_EXPR:
        <rdf:Description rdf:about="{fme:get-attribute("uri")}">
          <p:Attributen_201>{fme:get-attribute("IDENTIFICATIE")}</p:Attributen_201>
          <p:Attributen_523 rdf:resource="{fme:get-attribute("gebruiksfunctie_uri")}"/>
          <p:Attributen_419>{fme:get-attribute("VERHARDING")}</p:Attributen_419>
          <p:Attributen_345>{fme:get-attribute("WEGTYPE")}</p:Attributen_345>
          <p:JaarDeklaag rdf:datatype="http://www.w3.org/2001/XMLSchema#gYear">{fme:get-attribute("JAARDEKLAAG")}</p:JaarDeklaag>
          <p:JaarAanleg rdf:datatype="http://www.w3.org/2001/XMLSchema#gYear">{fme:get-attribute("JAARAANLEG")}</p:JaarAanleg>
          <p:Opp rdf:datatype="http://www.w3.org/2001/XMLSchema#float">{fme:get-attribute("SHAPE_Area")}</p:Opp>
          <p:Type rdf:datatype="http://www.w3.org/2001/XMLSchema#float">{fme:get-attribute("TYPESPEC")}</p:Type>
          <p:Traject>{fme:get-attribute("CODE")}</p:Traject>
          <p:Stroefheid>{fme:get-attribute("STROEFHEID")}</p:Stroefheid>
          <p:StroefheidDate rdf:datatype="http://www.w3.org/2001/XMLSchema#date">{fme:get-attribute("STROEFHEID_DATE")}</p:StroefheidDate>
          <p:Spoorvorming>{fme:get-attribute("SPOORVORMING")}</p:Spoorvorming>
          <p:SpoorvormingDate rdf:datatype="http://www.w3.org/2001/XMLSchema#date">{fme:get-attribute("SPOORVORMING_DATE")}</p:SpoorvormingDate>
          <p:Langsonvlakheid>{fme:get-attribute("LANGSONVLAKHEID")}</p:Langsonvlakheid>
          <p:LangsonvlakheidDate rdf:datatype="http://www.w3.org/2001/XMLSchema#date">{fme:get-attribute("LANGSONVLAKHEID_DATE")}</p:LangsonvlakheidDate>
          <p:Dwarsonvlakheid>{fme:get-attribute("DWARSONVLAKHEID")}</p:Dwarsonvlakheid>
          <p:DwarsonvlakheidDate rdf:datatype="http://www.w3.org/2001/XMLSchema#date">{fme:get-attribute("DWARSONVLAKHEID_DATE")}</p:DwarsonvlakheidDate>
          <geo:sfEquals rdf:resource="http://bgt.basisregistraties.overheid.nl/bgt/id/Wegdeel/{fme:get-attribute("lokaalid")}"/>
          <rdf:type rdf:resource="http://linkeddata.crow.nl/otl-bim-pro-imbor/def/objecttype/Objecttypes_401"/>
          <rdf:type rdf:resource="http://linkeddata.crow.nl/otl-bim-pro-imbor/def/objecttype/{fme:get-attribute("verh_cat")}"/>
          <rdfs:label>{fme:get-attribute("IDENTIFICATIE")}</rdfs:label>
        </rdf:Description>
    VISIBLE_QUERY_VALIDATE = Yes
    -> XMLFormatter
Note: Pretty-print and check validity
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = text_line_data
    XML_INPUT_TYPE = Attribute Specifying XML Text
    XML_OUTPUT_ATTR = text_line_data
    XML_OUTPUT_TYPE = Attribute
    PASSED -> XMLFormatter_Passed
    PASSED -> text_line (writer TEXTLINE_1)
    FAILED -> XMLFormatter_Failed
XMLFormatter_Passed: Inspector
XMLFormatter_Failed: Inspector
text_line (writer TEXTLINE_1)
    attributes: text_line_data buffer
